/********************************************************************************
 * Copyright (c) 2025 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package ConfigDaemon

import ScoreReq
import AssumedSystemRequirements

section "Application" {

    /* broken_link_c/issue/12990991 */
    ScoreReq.CompReq StorageAccessibility {
        description = '''Files persisted by ConfigDaemon shall be writable by ConfigDaemon only.'''
        safety = ScoreReq.Asil.B
        derived_from = [ConfigDaemon.SampleRequirementFeat@1]
        version = 1
        fulfilledBy = "ConfigDaemon"
    }

    /* broken_link_c/issue/14351696 */
    ScoreReq.CompReq StorageFailure {
        description = '''In case file system is not accessible for ConfigDaemon application at startup or any other failure leads to parameter data model populated incompletely, ConfigDaemon application shall not offer any services.'''
        safety = ScoreReq.Asil.B
        derived_from = [ConfigDaemon.SampleRequirementFeat@1]
        version = 1
        fulfilledBy = "ConfigDaemon"
    }

    ScoreReq.CompReq Lifecycle {
        description = '''{{ConfigDaemon}} shall implement {{Initialize()}} and {{Run()}} functions in order to be managed by {{LifecycleManager}}.'''
        safety = ScoreReq.Asil.QM
        derived_from = [ConfigDaemon.SampleRequirementFeat@1]
        version = 1
        fulfilledBy = "ConfigDaemon"
    }

    section "ApplicationStages" {

        ScoreReq.CompReq InitializePlugins {
            description = '''The {{ConfigDaemon}} shall setup {{Plugins}} during the execution of {{ConfigDaemon::Initialize()}}. The setup consists of the following steps:
            * Create {{Plugins}} by using {{PluginCollector}}.
            * Store created {{Plugins}} in internall collection.
            * Call the {{Initialize()}} function exactly once for each {{Plugin}} in the collection.'''
            safety = ScoreReq.Asil.QM
            derived_from = [ConfigDaemon.SampleRequirementFeat@1]
            version = 1
            fulfilledBy = "ConfigDaemon"
        }

        ScoreReq.CompReq InitializeService {
            description = '''The {{ConfigDaemon}} shall create and initialize {{InternalConfigProviderService}} service during the execution of {{ConfigDaemon::Initialize()}}.'''
            safety = ScoreReq.Asil.QM
            derived_from = [ConfigDaemon.SampleRequirementFeat@1]
            version = 1
            fulfilledBy = "ConfigDaemon"
        }

        ScoreReq.CompReq RunPlugins {
            description = '''The {{ConfigDaemon}} shall call the {{Run()}} function exactly once for each {{Plugin}} in the collection during the execution of {{ConfigDaemon::Run()}}.'''
            safety = ScoreReq.Asil.QM
            derived_from = [ConfigDaemon.SampleRequirementFeat@1]
            version = 1
            fulfilledBy = "ConfigDaemon"
        }

        ScoreReq.CompReq RunService {
            description = '''The {{ConfigDaemon}} shall offer {{InternalConfigProviderService}} service during the execution of {{ConfigDaemon::Run()}}.'''
            safety = ScoreReq.Asil.QM
            derived_from = [ConfigDaemon.SampleRequirementFeat@1]
            version = 1
            fulfilledBy = "ConfigDaemon"
        }

        ScoreReq.CompReq RunIdle {
            description = '''Following Run activity finalization, {{ConfigDaemon}} shall remain locked in an idle state until {{stop_token}} is modified.'''
            safety = ScoreReq.Asil.QM
            derived_from = [ConfigDaemon.SampleRequirementFeat@1]
            version = 1
            fulfilledBy = "ConfigDaemon"
        }

        ScoreReq.CompReq RunShutdown {
            description = '''{{ConfigDaemon}} shall process {{stop_token}} to interrupt any waiting and initiate the application shutdown.'''
            safety = ScoreReq.Asil.QM
            derived_from = [ConfigDaemon.SampleRequirementFeat@1]
            version = 1
            fulfilledBy = "ConfigDaemon"
        }

        ScoreReq.CompReq ShutdownPlugins {
            description = '''The {{ConfigDaemon}} shall call the {{Deinitialize()}} function exactly once for each {{Plugin}} in the collection during the execution of {{ConfigDaemon}} shutdown.'''
            safety = ScoreReq.Asil.QM
            derived_from = [ConfigDaemon.SampleRequirementFeat@1]
            version = 1
            fulfilledBy = "ConfigDaemon"
        }

        ScoreReq.CompReq ShutdownService {
            description = '''The {{ConfigDaemon}} shall stop offering {{InternalConfigProviderService}} during the execution of {{ConfigDaemon}} shutdown.'''
            safety = ScoreReq.Asil.QM
            derived_from = [ConfigDaemon.SampleRequirementFeat@1]
            version = 1
            fulfilledBy = "ConfigDaemon"
        }

    }

}

section "ParameterSetService" {

    /* broken_link_c/issue/23162017 */
    /*ScoreReq.CompReq ParameterSetServiceAvailability {
        description = '''{{ParameterSetService}} shall be available once the Data Model is complete.

        Note: Complete means that any existing Parameter Set is no longer extended and no further Parameter Set is added.'''
        safety = ScoreReq.Asil.B
        derived_from = [ConfigDaemon.SampleRequirementFeat@1]
        version = 1
        fulfilledBy = "ConfigDaemon"
    }*/

    /* broken_link_c/issue/22912892 */
    ScoreReq.CompReq ParameterSetServiceOffering {
        description = '''Component shall offer a Parameter Set Service, which allows to query a Parameter Set with its Parameter Set Qualifier from the Data Model.'''
        safety = ScoreReq.Asil.B
        derived_from = [ConfigDaemon.SampleRequirementFeat@1]
        version = 1
        fulfilledBy = "ConfigDaemon"
    }

}

section "DataModel" {

    /* broken_link_c/issue/21557384 */
    ScoreReq.CompReq DataModel {
        description = '''DataModel is a collection of Parameter Sets, which can be added by the Plugins.'''
        safety = ScoreReq.Asil.QM
        derived_from = [ConfigDaemon.SampleRequirementFeat@1]
        version = 1
        fulfilledBy = "ConfigDaemon"
    }

    /* broken_link_c/issue/23162088 */
    ScoreReq.CompReq ParameterSets {
        description = '''Parameters are grouped into Parameter Sets, which enables clients to obtain an aggregated state of all values within that set.'''
        safety = ScoreReq.Asil.QM
        derived_from = [ConfigDaemon.SampleRequirementFeat@1]
        version = 1
        fulfilledBy = "ConfigDaemon"
    }

    section "SupportedParameterTypes" {

        /* broken_link_c/issue/23162842 */
        ScoreReq.CompReq PrimitiveTypes {
            description = '''Following primitive parameter types shall be supported:
            * {{bool}}
            * {{sint8}}
            * {{sint16}}
            * {{sint32}}
            * {{sint64}}
            * {{uint8}}
            * {{uint16}}
            * {{uint32}}
            * {{uint64}}
            * {{float32}}
            * {{float64}}

            Note: This only applies to the Daemon Application. Plugins may also only support a subset of the types.'''
            safety = ScoreReq.Asil.QM
            derived_from = [ConfigDaemon.SampleRequirementFeat@1]
            version = 1
            fulfilledBy = "ConfigDaemon"
        }

        /* broken_link_c/issue/23162843 */
        ScoreReq.CompReq ComplexTypes {
            description = '''Following complex parameter types shall be supported:
            * One dimensional arrays of {{SupportedParameterTypes::PrimitiveTypes}}
            * Two dimensional arrays of {{SupportedParameterTypes::PrimitiveTypes}}

            Note: This only applies to the Daemon Application. Plugins may also only support a subset of the types.'''
            safety = ScoreReq.Asil.QM
            derived_from = [ConfigDaemon.SampleRequirementFeat@1]
            version = 1
            fulfilledBy = "ConfigDaemon"
        }

    }

    /* broken_link_c/issue/23162145 */
    ScoreReq.CompReq ParameterSetQualifier {
        description = '''The ParameterSet qualifier shall be restricted to one of the following states: {{DEFAULT}}, {{QUALIFIED}}, {{UNQUALIFIED}} or {{MODIFIED}}. Any other value is invalid.'''
        safety = ScoreReq.Asil.B
        derived_from = [ConfigDaemon.SampleRequirementFeat@1]
        version = 1
        fulfilledBy = "ConfigDaemon"
    }

}

section "Plugins" {

    ScoreReq.CompReq PluginResponsibility {
        description = '''{{Plugin}} components are responsible for populating or modifing the contents of the {{ParameterSetCollection}}.'''
        safety = ScoreReq.Asil.QM
        derived_from = [ConfigDaemon.SampleRequirementFeat@1]
        version = 1
        fulfilledBy = "ConfigDaemon"
    }

    ScoreReq.CompReq PluginSingleParametersType {
        description = '''{{Plugin}} shall process parameters of only one kind, e.g. coding or calibration or custom type of parameters.'''
        safety = ScoreReq.Asil.QM
        derived_from = [ConfigDaemon.SampleRequirementFeat@1]
        version = 1
        fulfilledBy = "ConfigDaemon"
    }

    ScoreReq.CompReq PluginCreation {
        description = '''{{Plugin}} shall register its own {{PluginCreator}} in {{PluginCollector}} in order to be created.'''
        safety = ScoreReq.Asil.QM
        derived_from = [ConfigDaemon.SampleRequirementFeat@1]
        version = 1
        fulfilledBy = "ConfigDaemon"
    }

    ScoreReq.CompReq PluginInitialization {
        description = '''{{Plugin}} shall implement the {{Initialize()}} function in a non-blocking manner.'''
        safety = ScoreReq.Asil.QM
        derived_from = [ConfigDaemon.SampleRequirementFeat@1]
        version = 1
        fulfilledBy = "ConfigDaemon"
    }

    ScoreReq.CompReq PluginRun {
        description = '''{{Plugin}} recieves handles to the {{ParameterSetCollection}} and to the {{InternalConfigProviderService}} within {{Run}} method.
        This handles should be used to update the database and notify clients about parameter and qualifier changes.'''
        safety = ScoreReq.Asil.QM
        derived_from = [ConfigDaemon.SampleRequirementFeat@1]
        version = 1
        fulfilledBy = "ConfigDaemon"
    }

}
