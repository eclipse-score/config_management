/********************************************************************************
 * Copyright (c) 2026 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package ConfigProvider

import ConfigManagement
import ScoreReq

section "ConfigProvider_Component_Requirements" {

    section "config_provider" {

        section "Notification" {

            /* broken_link_c/issue/23162623 */
            ScoreReq.CompReq CallbackTriggeredOnServiceAvailable {
                description = '''{{ConfigProvider}} shall notify the user application once {{InternalConfigProviderService}} is available.

                Note:
                The callback indicates that:
                * The service has been found
                * ConfigProvider is ready to access ParameterSets'''
                safety = ScoreReq.Asil.QM
                derived_from = [ConfigManagement.ConfigProviderInterface@1, ConfigManagement.ParameterSetAccess@1]
                version = 1
            }

        }

        section "ParameterSet_Access" {

            /* broken_link_c/issue/32233418 */
            ScoreReq.CompReq OnChangedParameterSetNotInvokedForSameData {
                description = '''The user application shall be notified not only when the Parameter Set's value changed but also when its {{ParameterSetQualifier}} changed.'''

                safety = ScoreReq.Asil.B
                derived_from = [ConfigManagement.ParameterSetAccess@1, ConfigManagement.ParameterSetQualifier@1, ConfigManagement.CompleteParameterSets@1]
                version = 1
            }

            ScoreReq.CompReq ParameterSetRetrievalWithTimeout {
                description = '''{{ConfigProvider}} shall support a timeout parameter when retrieving a Parameter Set to limit the maximum waiting time.'''
                safety = ScoreReq.Asil.QM
                derived_from = [ConfigManagement.ParameterSetAccess@1, ConfigManagement.ConfigProviderInterface@1]
                version = 1
            }

            ScoreReq.CompReq BatchParameterSetRetrieval {
                description = '''{{ConfigProvider}} shall enable retrieval of multiple Parameter Sets in a single request.'''
                safety = ScoreReq.Asil.B
                derived_from = [ConfigManagement.ConfigProviderInterface@1, ConfigManagement.CompleteParameterSets@1]
                version = 1
            }

        }

        section "Connection_Management" {

            ScoreReq.CompReq WaitUntilServiceConnected {
                description = '''{{ConfigProvider}} shall provide a mechanism to wait until the service connection is available, with timeout and cancellation support.'''
                safety = ScoreReq.Asil.QM
                derived_from = [ConfigManagement.ConfigProviderInterface@1]
                version = 1
            }

        }

        section "InitialQualifierState_Management" {

            ScoreReq.CompReq InitialQualifierStateUndefined {
                description = '''{{ConfigProvider}} as part of a user application shall initialize the {{InitialQualifierState}} with value {{UNDEFINED}} at its side, which will remain as long as no update is available from {{ConfigDaemon}} application.'''
                safety = ScoreReq.Asil.B
                derived_from = [ConfigManagement.ConfigProviderInterface@1, ConfigManagement.ParameterInitialQualifier@1]
                version = 1
            }

            ScoreReq.CompReq GetInitialQualifierStateWithTimeout {
                description = '''{{ConfigProvider}} shall provide the {{InitialQualifierState}} with timeout support.'''
                safety = ScoreReq.Asil.B
                derived_from = [ConfigManagement.ConfigProviderInterface@1, ConfigManagement.ParameterInitialQualifier@1]
                version = 1
            }

            ScoreReq.CompReq InitialQualifierStateChangeNotification {
                description = '''The user application shall be notified when the {{InitialQualifierState}} changes.'''
                safety = ScoreReq.Asil.B
                derived_from = [ConfigManagement.ConfigProviderInterface@1, ConfigManagement.ParameterInitialQualifier@1]
                version = 1
            }

        }

        section "Error_Handling" {

            ScoreReq.CompReq OperationErrorReporting {
                description = '''{{ConfigProvider}} operations related to {{InitialQualifierState}} shall indicate success or failure with error information so that the caller can react safely in case of failure.'''
                safety = ScoreReq.Asil.B
                derived_from = [ConfigManagement.ConfigProviderInterface@1, ConfigManagement.ParameterInitialQualifier@1]
                version = 1
            }

        }

    }

    section "parameter_set" {

        /* broken_link_c/issue/14602333 */
        ScoreReq.CompReq ParameterSetGetQualifier {
            description = '''{{ConfigProvider}} shall enable a user application to request a Parameter Set with its {{ParameterSetQualifier}} from the {{InternalConfigProviderService}}.'''
            safety = ScoreReq.Asil.B
            derived_from = [ConfigManagement.ConfigProviderInterface@1, ConfigManagement.ParameterSetQualifier@1]
            version = 1
        }

    }

    section "proxies" {

        section "InternalConfigProvider" {

            /* broken_link_c/issue/11397333 */
            ScoreReq.CompReq GetInitialQualifierState {
                description = '''A qualifier shall be offered to indicate the integrity of coding data for coding parameters which are attributed with ASIL B level.

                Note: ConfigDaemon assumes that functions which are using the coding parameters will establish a safe state in case when such qualifier indicates that coding data not in state Qualified.'''
                safety = ScoreReq.Asil.B
                derived_from = [ConfigManagement.ConfigProviderInterface@1, ConfigManagement.ParameterInitialQualifier@1]
                version = 1
            }

            ScoreReq.CompReq DefinitionMaxArgument {
                description = '''User specific maximal parameter set name length to be used as method argument shall be determined according to the parameter set list provided by user application. A parameter set name shall only be considered if it's contained in the buffer needs configuration `buffer_size_needs.json`. If there is no valid input for parameter set list provided, maximal length shall be the one of the overall longest parameter set name from the buffer needs configuration.'''
                safety = ScoreReq.Asil.B
                derived_from = [ConfigManagement.ParameterSetAquisitionAvailability@1]
                version = 1
            }

            ScoreReq.CompReq DefinitionUserSpecificMaxRetValue {
                description = '''User specific largest parameter set payload to be used as maximal method return value shall be determined according to the parameter set list provided by user application. A parameter set name shall only be considered if it's contained in the buffer needs configuration `buffer_size_needs.json`. If there is no valid input for parameter set list provided, largest parameter set payload size shall be the one of the overall largest parameter set payload from the buffer needs configuration.'''
                safety = ScoreReq.Asil.B
                derived_from = [ConfigManagement.ParameterSetAquisitionAvailability@1]
                version = 1
            }

            ScoreReq.CompReq AdditionalProxyNeedsRegistration {
                description = '''Memory buffer needs shall be passed as `additional_shm_size` argument to proxy construction method. The needs are equal to the sum of:
                * User specific maximal parameter set name length, and
                * User specific largest parameter set payload size.'''
                safety = ScoreReq.Asil.B
                derived_from = [ConfigManagement.ParameterSetAquisitionAvailability@1]
                version = 1
            }

            ScoreReq.CompReq ReservePsNameArgumentBuffer {
                description = '''User specific maximal parameter set name length shall be reserved exactly once as memory buffer for the `parameter set name` method's argument.'''
                safety = ScoreReq.Asil.B
                derived_from = [ConfigManagement.ParameterSetAquisitionAvailability@1]
                version = 1
            }

            ScoreReq.CompReq GuardPsNameArgumentBuffer {
                description = '''Parameter set name shall only be passed as argument if it's smaller or equal to the user specific maximal parameter set name length. Otherwise, no method calls with this parameter set name shall take place and an error shall be raised.'''
                safety = ScoreReq.Asil.B
                derived_from = [ConfigManagement.ParameterSetAquisitionAvailability@1]
                version = 1
            }

            ScoreReq.CompReq PassMaxPayloadSizeArg {
                description = '''Client shall pass the user specific largest parameter set payload size to server as argument of GetParameterSet() method of InternalConfigProvider service.'''
                safety = ScoreReq.Asil.B
                derived_from = [ConfigManagement.ParameterSetAquisitionAvailability@1]
                version = 1
            }

        }

    }

}
