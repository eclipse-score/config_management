/********************************************************************************
 * Copyright (c) 2025 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package AssumedSystemRequirements

import ScoreReq

ScoreReq.AssumedSystemReq SafeConfiguration {
    description = """The SW-platform shall support safe configuration.

Note: This is part of 0.5 release and therefore can only support ASIL_B. Goal is ASIL_D."""
    safety = ScoreReq.Asil.B
    rationale = "Configuration files may hold safety relevant information."
    version = 1
}

ScoreReq.AssumedSystemReq FileBasedConfiguration {
    description = """The SW-platform shall support configuration of applications via files (e.g. yaml, json)."""
    safety = ScoreReq.Asil.QM
    rationale = "File based configuration allows changes without rebuilding the software."
    version = 1
}
